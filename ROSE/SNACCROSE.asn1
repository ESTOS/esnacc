SNACC-ROSE {joint-iso-itu-t remote-operations(4) informationObjects(5) version1(0) }

DEFINITIONS ::= BEGIN

--ROSE specific things...
ROSEMessage ::= CHOICE {
	invoke [1] IMPLICIT ROSEInvoke,
	result [2] IMPLICIT ROSEResult,
	error  [3] IMPLICIT ROSEError,
	reject [4] IMPLICIT ROSEReject
}

ROSEAuth ::= SEQUENCE {
	method UTF8String,            -- Authentication Type (e.g. "Basic" or "JWT")
	authdata OCTET STRING,         -- Authentication Data z.b. BASE64(user:passwd) or jwt string or NTLM binary 
	...
}

ROSEAuthList ::= SEQUENCE OF ROSEAuth 

ROSEAuthRequest ::= SEQUENCE {
	auth ROSEAuth,
	context  UTF8String OPTIONAL,  -- Auth context for multi-level negotiation must be supplied again by the client on the second call
	...
}

ROSEAuthResult ::= SEQUENCE {
	authList ROSEAuthList,
	context  UTF8String OPTIONAL,  -- Auth context for multi-level negotiation must be supplied again by the client on the second call
	...
}

ROSEInvoke		::=	SEQUENCE {
	sessionID [1] UTF8String OPTIONAL,
	invokeID INTEGER,
	linked-ID [0] IMPLICIT INTEGER OPTIONAL,
	operationName [2] UTF8String OPTIONAL,
	authentication [3] ROSEAuthRequest OPTIONAL,
	-- Relative client-requested deadline in milliseconds.
	-- Evaluated on the server at receive time: deadline = T_receive + timeout.
	-- If the server cannot process the invoke in time (e.g. queued behind resource
	-- limits) and the deadline has passed after receipt, the request is neither
	-- executed nor answered (no late result/error/reject for that expired work).
	timeout [4] IMPLICIT INTEGER OPTIONAL,
	operationID INTEGER,
	argument ANY OPTIONAL
}

ROSEResult ::= SEQUENCE {
	sessionID [1] UTF8String OPTIONAL,
	invokeID INTEGER,
	result SEQUENCE {
		resultValue INTEGER,
		result ANY,
		...
	} OPTIONAL,
	...
}

ROSEError ::= SEQUENCE {
	sessionID [1] UTF8String OPTIONAL,
	invokedID INTEGER,
	error-value INTEGER,
	error ANY OPTIONAL
}

ROSEReject ::= SEQUENCE {
	sessionID [1] UTF8String OPTIONAL,
	invokedID CHOICE {
		invokedID INTEGER,
		invokednull NULL
	},
	reject RejectProblem OPTIONAL,
	details UTF8String OPTIONAL, -- ste Added 24.10.2014 not Rose Standard, used for Json Decode Error
	authentication [4] ROSEAuthResult OPTIONAL, -- ste Added 21.10.2015 not Rose Standard, used for Invoke Authentication
	...
}

RejectProblem ::= CHOICE {
	generalProblem [0] IMPLICIT GeneralProblem,
	invokeProblem  [1] IMPLICIT InvokeProblem,
	returnResultProblem [2] IMPLICIT ReturnResultProblem,
	returnErrorProblem [3] IMPLICIT ReturnErrorProblem
}

GeneralProblem ::= INTEGER { -- ROSE-provider detected
	unrecognisedAPDU(0),
	mistypedAPDU(1),
	badlyStructuredAPDU(2)
}

InvokeProblem ::= INTEGER { -- ROSE-user detected
	duplicateInvocation(0),
	unrecognisedOperation(1), -- Detail "unrecognisedOperation": operation is not in the generated stub or the lookup map (ROSE_REJECT_UNKNOWNOPERATION). Detail "functionMissing": operation is known, but the virtual OnInvoke handler is not overridden (ROSE_REJECT_FUNCTIONMISSING)
	mistypedArgument(2),
	resourceLimitation(3), -- Detail "queueFull": dispatch queue is full, handler did not run (ROSE_REJECT_QUEUE_FULL). Detail "responseIsTooBig": encoded response exceeds the length prefix (ROSE_TE_ENCODE_FAILED). Detail "functionMissing" is legacy for a missing OnInvoke override.
	initiatorReleasing(4),
	unrecognisedLinkedID(5),
	linkedResponseUnexpected(6),
	unexpectedChildOperation(7),
	invalidSessionID(8),          -- sessionID in Invoke is not valid
	authenticationIncomplete(9),  -- Invoke Authentication failed - second step required (Digest / NTLM) - look at ROSEAuth in Reject Message
	authenticationFailed(10)      -- Invoke Authentication failed  
}

ReturnResultProblem ::= INTEGER { -- ROSE-user detected
	unrecognisedInvocation(0),
	resultResponseUnexpected(1),
	mistypedResult(2)
}

ReturnErrorProblem ::= INTEGER { -- ROSE-user detected
	unrecognisedInvocation(0),
	errorResponseUnexpected(1),
	unrecognisedError(2),
	unexpectedError(3),
	mistypedParameter(4)
}

END
