Serializable-Test
	{ 1 3 6 1 4 1 10924 9999 98 }

DEFINITIONS
IMPLICIT TAGS ::=
BEGIN

AsnStatus ::= ENUMERATED
{
	active(0),
	inactive(1)
}

AsnUserId ::= UTF8String

AsnUserIds ::= SEQUENCE OF AsnUserId

AsnPerson ::= SEQUENCE
{
	name UTF8String,
	age [0] INTEGER OPTIONAL,
	avatar [1] OCTET STRING OPTIONAL,
	status AsnStatus,
	...
}

AsnPeopleList ::= SEQUENCE OF AsnPerson

AsnTaggedChoice ::= CHOICE
{
	text UTF8String,
	code INTEGER
}

END
