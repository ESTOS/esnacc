DeprecatedSuccessor-Test
	{ 1 3 6 1 4 1 10924 9999 98 }

DEFINITIONS
IMPLICIT TAGS ::=
BEGIN

-- @deprecated 01.01.2024 -> (none)
asnValidNone OPERATION
	ARGUMENT	arg NULL
	RESULT		res NULL
::= 9101

-- @deprecated 02.01.2024 -> asnValidSameFile
asnValidSameFile OPERATION
	ARGUMENT	arg NULL
	RESULT		res NULL
::= 9102

-- @deprecated 03.01.2024 -> UCWeb::asnGetTime
asnValidExternal OPERATION
	ARGUMENT	arg NULL
	RESULT		res NULL
::= 9103

-- @deprecated 04.01.2024 see asnValidSameFile
asnLegacyProse OPERATION
	ARGUMENT	arg NULL
	RESULT		res NULL
::= 9104

-- @deprecated 05.01.2024 -> asnMissingSymbol
asnMissingSuccessor OPERATION
	ARGUMENT	arg NULL
	RESULT		res NULL
::= 9105

-- @deprecated 06.01.2024
-- -> asnValidSameFile
asnSuccessorOnNextLine OPERATION
	ARGUMENT	arg NULL
	RESULT		res NULL
::= 9106

-- @deprecated 07.01.2024 -> DeprecatedSuccessor_Ref::asnValidTarget
asnValidCrossModule OPERATION
	ARGUMENT	arg NULL
	RESULT		res NULL
::= 9107

-- @deprecated 08.01.2024 -> DeprecatedSuccessor_Ref::asnMissingInRef
asnInvalidCrossModule OPERATION
	ARGUMENT	arg NULL
	RESULT		res NULL
::= 9108

AsnEnumMemberDeprecationEnum ::= ENUMERATED
{
	eLegacyEnumValue(1),	-- @deprecated 10.01.2024 legacy prose without canonical arrow
	eValidEnumValue(2)	-- @deprecated 11.01.2024 -> (none)
}

END
